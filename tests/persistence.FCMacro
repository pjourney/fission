# SPDX-License-Identifier: LGPL-2.1-or-later
"""Two separate native launches validate preferences and layout persistence.

FISSION_PERSISTENCE_PHASE=write then read; both launches use
Fission.exe -u <repo>/test-output/persistence.cfg tests/persistence.FCMacro.
"""

import importlib
import json
import os
from pathlib import Path
import sys
import traceback

import FreeCAD as App
import FreeCADGui as Gui
from PySide import QtCore, QtWidgets
try:
    from PySide import QtTest
except ImportError:
    try:
        QtTest = importlib.import_module("PySide6.QtTest")
    except ImportError:
        QtTest = importlib.import_module("PySide2.QtTest")

REPO = Path(os.environ.get("FISSION_SOURCE_ROOT", r"C:\Users\juice_box_local\Desktop\fission")).resolve()
OUTPUT = Path(os.environ.get("FISSION_TEST_OUTPUT", str(REPO / "test-output"))).resolve()
OUTPUT.mkdir(parents=True, exist_ok=True)
PHASE = os.environ.get("FISSION_PERSISTENCE_PHASE", "")


def require(condition, message):
    if not condition:
        raise AssertionError(message)


def settle(milliseconds=250):
    QtWidgets.QApplication.processEvents()
    QtTest.QTest.qWait(milliseconds)


def geometry_state(controller):
    return {
        "width": controller.main.width(),
        "height": controller.main.height(),
        "x": controller.main.x(),
        "y": controller.main.y(),
        "maximized": controller.main.isMaximized(),
        "browser_width": controller.browser.width(),
        "timeline_height": controller.timeline.height(),
        "browser_visible": controller.browser.isVisible(),
        "timeline_visible": controller.timeline.isVisible(),
    }


def run_persistence_phase():
    report_file = OUTPUT / "persistence-report.json"
    controller = None
    if report_file.is_file() and PHASE == "read":
        report = json.loads(report_file.read_text(encoding="utf-8"))
    else:
        report = {"profile": str(OUTPUT / "persistence.cfg"), "phases": {}}
    result = {"phase": PHASE, "status": "failed"}
    try:
        require(PHASE in ("write", "read"), "Set FISSION_PERSISTENCE_PHASE to write or read")
        profile = Path(App.ConfigGet("UserParameter")).resolve()
        require(profile == (OUTPUT / "persistence.cfg").resolve(), "Persistence test requires isolated -u test-output/persistence.cfg")
        require(not App.listDocuments(), "Persistence launch must start without open design documents")
        Gui.activateWorkbench("FissionWorkbench")
        from fission.shell import get_controller
        from fission.preferences import PreferencesDialog
        from fission.shortcuts import ShortcutProfile
        from fission.marking_config import read_config, write_config
        controller = get_controller()
        controller.main.show()
        controller.main.activateWindow()
        controller.main.raise_()
        settle(350)
        if PHASE == "write":
            controller.main.showNormal()
            controller.main.resize(1280, 800)
            controller.main.move(100, 75)
            controller.browser.show()
            controller.timeline.show()
            # Launch actual toolbox commands with Return; recents must survive
            # a different application process, not just this dialog instance.
            for _ in range(2):
                controller.perform("Search")
                settle(80)
                toolbox = controller.search_dialog
                toolbox.input.setText("Browser")
                item = next(toolbox.results.topLevelItem(index)
                            for index in range(toolbox.results.topLevelItemCount())
                            if toolbox.results.topLevelItem(index).data(0, QtCore.Qt.UserRole) == "Fission_ToggleBrowser")
                toolbox.results.setCurrentItem(item)
                QtTest.QTest.keyClick(toolbox.input, QtCore.Qt.Key_Return)
                settle(100)
                require(not toolbox.isVisible(), "A successful toolbox command must close search")
            require(controller.browser.isVisible(), "Two real Browser toggles must restore the original visibility")
            require("Fission_ToggleBrowser" in controller.settings.GetString("CommandSearchHistory", ""),
                    "Successful toolbox launches must persist command history")
            preferences = PreferencesDialog(controller, controller.main)
            preferences.theme.setCurrentText("Light")
            preferences.navigation.setCurrentIndex(preferences.navigation.findData("Gui::CADNavigationStyle"))
            preferences.accept()  # Exercise the public preference commit without opening a modal dialog.
            marking = read_config(controller.settings)
            marking["enabled"] = False
            marking["slots"]["model"][0] = "Fission_Fit"
            marking["slots"]["model"][1] = ""
            marking["slots"]["mesh"][7] = "FutureWorkbench_CustomCommand"
            write_config(controller.settings, marking)
            controller.marking.refresh_settings()
            controller.shortcuts.set_binding("Fission_Fillet", "Alt+F")
            view_parameters = App.ParamGet("User parameter:BaseApp/Preferences/View")
            if view_parameters.GetBool("ShowNaviCube", True):
                controller.perform("ToggleViewCube")
            if controller.nav_dock.isVisible():
                controller.perform("ToggleNavigation")
            controller.main.resizeDocks([controller.browser], [365], QtCore.Qt.Horizontal)
            controller.main.resizeDocks([controller.timeline], [180], QtCore.Qt.Vertical)
            settle(350)
            controller.save_layout()
            App.saveParameter()
            require(profile.is_file(), "First process must save its actual isolated user profile")
            require(controller.settings.GetString("Theme", "") == "Light", "Light theme must be stored")
            require(controller.settings.GetString("Navigation", "") == "Gui::CADNavigationStyle", "Alternate navigation must be stored")
            require(controller.shortcuts.shortcut_for("Fission_Fillet", "model") == "Alt+F", "Custom model F shortcut must be stored")
            require(not view_parameters.GetBool("ShowNaviCube", True), "Hidden native cube preference must be stored")
            require(not controller.nav_dock.isVisible() and not controller.settings.GetBool("ShowNavigation", True),
                    "Hidden navigation bar must be applied and stored")
            require(bool(controller.settings.GetString("Geometry", "")) and bool(controller.settings.GetString("Layout", "")), "Both native window geometry and dock state must be stored")
            geometry = geometry_state(controller)
            require(abs(geometry["browser_width"] - 365) < 40, "Browser width request must be applied before save")
            result.update({"status": "passed", "theme": "Light", "navigation": "Gui::CADNavigationStyle", "fillet_shortcut": "Alt+F", "view_cube_visible": False, "navigation_bar_visible": False, "geometry": geometry, "layout": controller.settings.GetString("Layout", ""), "window_geometry": controller.settings.GetString("Geometry", ""), "config_bytes": profile.stat().st_size, "process_id": os.getpid()})
        else:
            written = report["phases"]["write"]
            require(written["status"] == "passed", "A successful write process must precede read")
            require(written["process_id"] != os.getpid(), "Read validation must run in a genuinely separate process")
            require(controller.settings.GetString("Theme", "") == "Light", "Light theme must survive application restart")
            controller.perform("Search")
            settle(80)
            toolbox = controller.search_dialog
            require(toolbox.results.topLevelItem(0).data(0, QtCore.Qt.UserRole) == "Fission_ToggleBrowser",
                    "A new process must load successful toolbox history into the first available result")
            result["search_history_restart"] = "Fission_ToggleBrowser"
            toolbox.close()
            settle(80)
            marking = read_config(controller.settings)
            require(not marking["enabled"] and marking["slots"]["model"][:2] == ["Fission_Fit", ""],
                    "Disabled marking menu and custom/empty slots must survive a separate process restart")
            require(marking["slots"]["mesh"][7] == "FutureWorkbench_CustomCommand",
                    "Unavailable command IDs must remain stored after restart")
            require(controller.marking.config == marking, "Restarted menu must load the actual persisted configuration")
            result["marking_restart"] = {"enabled": False, "model_north": "Fission_Fit", "model_northeast": "",
                                         "mesh_northwest": "FutureWorkbench_CustomCommand"}
            require("#f5f7f9" in controller.main.styleSheet(), "Restored Light theme must be applied to real Qt widgets")
            require(controller.settings.GetString("Navigation", "") == "Gui::CADNavigationStyle", "Alternate navigation must survive restart")
            view_parameters = App.ParamGet("User parameter:BaseApp/Preferences/View")
            require(view_parameters.GetString("NavigationStyle", "") == "Gui::CADNavigationStyle", "Native view navigation preference must survive restart")
            require(not view_parameters.GetBool("ShowNaviCube", True), "Hidden cube preference must survive restart")
            require(not controller.nav_dock.isVisible() and not controller.settings.GetBool("ShowNavigation", True),
                    "Hidden navigation bar must survive restart in the actual Qt window")
            require(controller.shortcuts.shortcut_for("Fission_Fillet", "model") == "Alt+F", "Custom model F mapping must load in the new manager")
            independently_loaded = ShortcutProfile()
            independently_loaded.load(controller.shortcuts.parameters)
            require(independently_loaded.overrides.get("Fission_Fillet") == "Alt+F", "Disk ParamGet profile must match the restored runtime shortcut")
            require(controller.settings.GetString("Layout", "") == written["layout"], "Persisted native dock state must match the writer")
            require(controller.settings.GetString("Geometry", "") == written["window_geometry"], "Persisted native window state must match the writer")
            geometry = geometry_state(controller)
            for name, tolerance in (("width", 20), ("height", 30), ("x", 35), ("y", 35), ("browser_width", 35), ("timeline_height", 35)):
                require(abs(geometry[name] - written["geometry"][name]) <= tolerance, "Restored {} differs: written {}, read {}".format(name, written["geometry"][name], geometry[name]))
            for name in ("maximized", "browser_visible", "timeline_visible"):
                require(geometry[name] == written["geometry"][name], "Restored state differs: " + name)
            require(not App.listDocuments(), "Preferences/layout test must remain independent of CAD documents")
            # A transient empty native viewer verifies the persisted cube policy
            # on a newly created document; no CAD geometry or document is saved.
            probe = App.newDocument("PersistedNativeCubePolicy")
            try:
                settle(120)
                require(not Gui.activeDocument().activeView().getViewer().isEnabledNaviCube(),
                        "A fresh native 3D viewer must apply the persisted hidden cube preference")
            finally:
                App.closeDocument(probe.Name)
                settle(100)
            controller.main.grab().save(str(OUTPUT / "fission-persistence-light.png"))
            result.update({"status": "passed", "theme": "Light", "navigation": "Gui::CADNavigationStyle", "fillet_shortcut": "Alt+F", "view_cube_visible": False, "navigation_bar_visible": False, "new_native_viewer_cube_visible": False, "geometry": geometry, "process_id": os.getpid()})
        App.Console.PrintMessage("FISSION PERSISTENCE {} PASS\n".format(PHASE))
    except Exception as exc:
        result.update({"error": str(exc), "traceback": traceback.format_exc()})
        App.Console.PrintError("FISSION PERSISTENCE {} FAIL: {}\n{}\n".format(PHASE, exc, result["traceback"]))
    finally:
        report["phases"][PHASE or "unknown"] = result
        report["passed"] = bool(report["phases"].get("write", {}).get("status") == "passed" and report["phases"].get("read", {}).get("status") == "passed")
        report_file.write_text(json.dumps(report, indent=2) + "\n", encoding="utf-8")
        (OUTPUT / ("persistence-{}-complete.txt".format(PHASE or "unknown"))).write_text("PASS\n" if result["status"] == "passed" else "FAIL\n", encoding="utf-8")
        if controller:
            controller.save_layout()
        QtCore.QTimer.singleShot(250, QtWidgets.QApplication.instance().quit)


QtCore.QTimer.singleShot(2000, run_persistence_phase)
